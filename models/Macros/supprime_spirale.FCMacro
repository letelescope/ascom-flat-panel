import FreeCAD as App

doc = App.ActiveDocument

for name in [
    "SpiralPath",
    "SpiralBinder",
    "GrooveProfile",
    "SpiralGroove",
    "CenterPocket",
    "CenterPocketCut"
]:
    obj = doc.getObject(name)
    if obj:
        doc.removeObject(name)

doc.recompute()
